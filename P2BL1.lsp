(defun c:P2B_Layer1 (/ blkName ss i en entData entType pt p1 p2 count)
(setvar "CMDECHO" 0)
(setq blkName (getstring "\n请输入要替换成的块名称: "))
(if (not (tblsearch "BLOCK" blkName))
(progn
(princ (strcat "\n错误：找不到名为 \"" blkName "\" 的块。"))
(exit)
)
)
(princ "\n请选择要替换的对象 (点/直线/多段线/圆/椭圆/块): ")
(setq ss (ssget '((0 . "POINT,LINE,LWPOLYLINE,CIRCLE,ELLIPSE,INSERT"))))
(if ss
(progn
(setq i 0)
(setq count (sslength ss))
(repeat count
(setq en (ssname ss i))
(setq entData (entget en))
(setq entType (cdr (assoc 0 entData)))
(cond
((member entType '("POINT" "CIRCLE" "INSERT" "ELLIPSE"))
(setq pt (cdr (assoc 10 entData))))
((equal entType "LINE")
(setq p1 (cdr (assoc 10 entData)))
(setq p2 (cdr (assoc 11 entData)))
(setq pt (list (/ (+ (car p1) (car p2)) 2.0)
(/ (+ (cadr p1) (cadr p2)) 2.0)
(/ (+ (caddr p1) (caddr p2)) 2.0))))
((equal entType "LWPOLYLINE")
(setq pt (cdr (assoc 10 entData))))
)
(if pt
(progn
(entmake (list 
'(0 . "INSERT") 
(cons 2 blkName) 
(cons 10 pt)
'(41 . 1.0)
'(42 . 1.0)
'(43 . 1.0)
))
(entdel en)
)
)
(setq i (1+ i))
)
(princ (strcat "\n成功！已将 " (itoa count) " 个物体替换为块 \"" blkName "\"。"))
)
(princ "\n未选中任何有效物体。")
)
(setvar "CMDECHO" 1)
(princ)
)
