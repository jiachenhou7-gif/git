(defun c:SINEFAST (/ ent p1 p2 len ang amp freq seg totalSeg i x y pt old_osmode)
(setq ent (car (entsel "\n请选择一条作为基准的直线: ")))
(if (and ent (= (cdr (assoc 0 (entget ent))) "LINE"))
(progn
(setq p1 (cdr (assoc 10 (entget ent))))
(setq p2 (cdr (assoc 11 (entget ent))))
(setq len (distance p1 p2))
(setq ang (angle p1 p2))
(setq amp 10.0)
(setq freq 5.0)
(setq seg 40)
(setq totalSeg (fix (* freq seg)))
(setq old_osmode (getvar "OSMODE"))
(setvar "OSMODE" 0)
(command "_.PLINE")
(setq i 0)
(while (<= i totalSeg)
(setq x (* len (/ (float i) totalSeg)))
(setq y (* amp (sin (* 2 pi freq (/ (float i) totalSeg)))))
(setq pt (polar (polar p1 ang x) (+ ang (/ pi 2)) y))
(command "_non" pt)
(setq i (1+ i))
)
(command "")
(setvar "OSMODE" old_osmode)
(entdel ent)
(princ "\n完美！正弦线已生成，原直线已自动删除。")
)
(princ "\n错误: 您选择的不是一条直线，请重新运行命令。")
)
(princ)
)
